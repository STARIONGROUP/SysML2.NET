package DependencyTest {
    package System {
        package 'Application Layer';
        package 'Service Layer';
        package 'Data Layer';
    }
    private import System::*;
    dependency Use from 'Application Layer' to 'Service Layer';
    dependency 'Service Layer' to 'Data Layer';
    attribute x;
    attribute y;
    attribute z;
    dependency z to x, y;
}
