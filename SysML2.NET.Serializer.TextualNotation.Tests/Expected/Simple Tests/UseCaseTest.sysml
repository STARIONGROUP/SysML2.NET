package UseCaseTest {
    part def System;
    part def User;
    use case def UseSystem {
        subject system: System;
        actor user: User;
        objective {
            /* Goal */
        }
        include use case uc1: UC1;
        include use case uc2 {
            subject = system;
            actor user = UseSystem::user;
        }
    }
    use case def UC1;
    part user: User;
    use case uc2 {
        subject;
        actor :>> user;
    }
    use case u: UseSystem;
    part system: System {
        include uc2;
        perform u;
        use case uc1: UC1;
    }
    use case uc3 {
        include u;
        include system.uc1;
    }
}
