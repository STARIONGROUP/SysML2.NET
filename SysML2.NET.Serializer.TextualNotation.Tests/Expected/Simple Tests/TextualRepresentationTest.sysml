package TextualRepresentationTest {
    private import ScalarValues::Real;
    item def C {
        attribute x: Real;
        assert constraint x_constraint { rep inOCL language "ocl"/* self.x > 0.0 */ }
    }
    action def setX {
        in c: C;
        in newX: Real;
        language "alf"/*
         * c.x = newX;
         * WriteLine("Set new x");
         */
    }
}
