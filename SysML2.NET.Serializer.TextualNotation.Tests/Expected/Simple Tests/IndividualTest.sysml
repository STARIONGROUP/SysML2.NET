package IndividualTest {
    individual def IO1;
    individual def IO2 {
        individual io: IO1;
    }
    individual item def II1 {
        individual item ii: II1;
    }
    item def I {
        part i: I;
    }
    individual item def II2 :> I {
        individual item :>> i : II2;
    }
    individual part def IP1 {
        individual part p: IP1;
    }
    part def P {
        part p: P;
    }
    individual part def IP2 :> P {
        individual part :>> p : IP2;
    }
    individual action def AP1 {
        individual action a: AP1;
    }
    action def A {
        action a: A;
    }
    individual action def IA2 :> A {
        individual action :>> a : IA2;
    }
}
