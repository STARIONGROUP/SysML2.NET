package Q {
    part def F {
        part a: A;
    }
    part f: F;
    part def A {
        part g = f.a;
    }
    part def B {
        part f: F;
        part a: A;
    }
    part def C {
        part b: B {
            connect f.a to a.g;
            bind f.a = a.g;
        }
        part c :> b.f {
            part aa :> a;
        }
        flow b.f.a to c.aa;
    }
    part e1 {
        attribute x: E;
        bind e1.x = E::e2;
    }
    enum def E {
        enum e1;
        enum e2;
    }
    part g = new A().g.g.g;
}
