/* AAA */
package CommentTest {
    /*
     * AAA
     * BBB*/
    /*
     *
     *
     * AAA  ***   
     * BBB
     */
    /*
     *       AAAA
     *       BBBB           */
    /*
     * AAAA
     *
     *
     * BBBB
     *
     * CCCC
     */
    locale "en_US" /*
     * AAAA
     * BBBB
     *    CCC DDD    
     */
    /* comment inside a package */
    doc locale "en_US"
    /* Documentation about Package */
    comment cmt /* Named Comment */
    comment cmt_cmt about cmt /* Comment about Comment */
    comment about C /* Documention Comment about Part Def */
    part def C {
        doc
        /* Documentation in Part Def */
        /* Comment in Part Def */
        comment about CommentTest locale "en_US" /* Comment about Package */
    }
    /* abc */
    part def A;
}
