package ConjugationTest {
    port def P;
    part def B {
        port p1: P;
        port p2: ~P;
    }
    connection def A {
        end port p1: P;
        end port p2: ~P;
    }
    interface def I {
        end p1: P;
        end p2: ~P;
    }
    part def B1 {
        part p {
            port p1: P;
            port p2: ~P;
        }
        connection a: A {
            end port p3: P ::> p.p1;
            end port p4: ~P ::> p.p2;
        }
        interface i: I {
            end p3: P ::> p.p1;
            end p4: ~P ::> p.p2;
        }
    }
}
