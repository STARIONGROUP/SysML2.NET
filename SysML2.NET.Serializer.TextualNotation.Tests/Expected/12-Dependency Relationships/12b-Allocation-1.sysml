package '12b-Allocation-1' {
    private import SI::*;
    private import RequirementModel::*;
    private import LogicalModel::*;
    private import PhysicalModel::*;
    package RequirementModel {
        requirement torqueGeneration {
            subject generator: TorqueGenerator;
            require constraint { generator.generateTorque.torque > 0.0[N * m] }
        }
    }
    package LogicalModel {
        action def GenerateTorque {
            out torque :> ISQ::torque;
        }
        part def LogicalElement;
        part def TorqueGenerator :> LogicalElement {
            perform action generateTorque: GenerateTorque;
        }
        action providePower {
            action generateTorque: GenerateTorque;
        }
        part torqueGenerator: TorqueGenerator {
            perform providePower.generateTorque :>> generateTorque;
        }
        assert satisfy torqueGeneration by torqueGenerator;
    }
    package PhysicalModel {
        part def PhysicalElement;
        part def PowerTrain :> PhysicalElement;
        part powerTrain: PowerTrain {
            part engine {
                perform providePower.generateTorque;
            }
        }
    }
    allocation def LogicalToPhysical {
        end ref logical: LogicalElement;
        end ref physical: PhysicalElement;
    }
    allocation torqueGenAlloc: LogicalToPhysical allocate logical ::> torqueGenerator to physical ::> powerTrain {
        allocate torqueGenerator.generateTorque to powerTrain.engine.generateTorque;
    }
}
