package '1a-Parts Tree' {
    private import SI::kg;
    package Definitions {
        part def Vehicle {
            attribute mass :> ISQ::mass {
                doc
                /*
                 * The 'mass' attribute property is declared here to be a 
                 * specialization (subset) of the general 'mass' quantity 
                 * from the 'ISQ' (International System of Quantities) 
                 * library model.
                 */

            }
        }
        part def AxleAssembly;
        part def Axle {
            attribute mass :> ISQ::mass;
        }
        part def FrontAxle :> Axle {
            attribute steeringAngle: ScalarValues::Real;
        }
        part def Wheel;
    }
    package Usages {
        private import Definitions::* {
            /*
             * A "private" private import makes the imported names private to the
             * imported package.
             */
        }
        part vehicle1: Vehicle {
            /*
             * 'vehicle1' is a package-owned part of type Vehicle.
             */
            attribute mass :>> Vehicle::mass = 1750[kg] {
                /*
                 * This redefines the 'mass' attribute property from 'Vehicle' to 
                 * give it a fixed attribute.
                 */
            }
            part frontAxleAssembly: AxleAssembly {
                /*
                 * 'frontAxleAssembly' is a nested part of part 'vehicle1'.
                 * It is a composite part of the containing part.
                 *
                 * (And similarly for 'rearAxleAssembly'.)
                 */
                part frontAxle: Axle;
                part frontWheel: Wheel[2] ordered {
                    /*
                     * 'frontWheel' is a nested part of type 'Wheel' with
                     * multiplicity "2". This means that this axle assembly
                     * must have exactly two wheels. However, there is still
                     * only one 'frontWheel' part. The part is "ordered",
                     * so that the first wheel can be distinguished from the
                     * second.
                     */
                }
            }
            part rearAxleAssembly: AxleAssembly {
                part rearAxle: Axle;
                part rearWheel: Wheel[2] ordered;
            }
        }
        part vehicle1_c1: Vehicle {
            /*
             * 'vehicle1_c1' is a modified copy of 'vehicle1'. There is no
             * connection between this copy and the original version in the
             * model.
             */
            attribute mass :>> Vehicle::mass = 2000[kg] {
                /*
                 * The mass attribute has been modified.
                 */
            }
            part frontAxleAssembly: AxleAssembly {
                part frontAxle: FrontAxle {
                    /*
                     * The part 'frontAxle' has been modified to have type 'FrontAxle'.
                     */
                }
                part frontWheel: Wheel[2] ordered {
                    /*
                     * The parts 'frontWheel_1' and 'frontWheel_2' have been added
                     * as subsets of 'frontWheel'. These are separate parts from
                     * 'frontWheel', but essentially provide alternate names for
                     * each of the two wheels, as given by their defining expressions.
                     */
                }
                part frontWheel_1 :> frontWheel = frontWheel#(1);
                part frontWheel_2 :> frontWheel = frontWheel#(2);
            }
            part rearAxleAssembly: AxleAssembly {
                /*
                 * 'rearAxleAssembly' has also been modified to add subsetting parts
                 * for 'rearWheel'.
                 */
                part rearAxle: Axle;
                part rearWheel: Wheel[2] ordered;
                part rearWheel_1 :> rearWheel = rearWheel#(1);
                part rearWheel_2 :> rearWheel = rearWheel#(2);
            }
        }
    }
}
