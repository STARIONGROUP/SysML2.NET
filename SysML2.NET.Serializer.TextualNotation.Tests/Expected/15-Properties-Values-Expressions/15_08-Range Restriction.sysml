package '15_08-Range Restriction' {
    private import ISQ::*;
    private import SI::*;
    private import '15_01-Constants'::'Mathematical Constants'::pi;
    part def HeadLightsTiltKnob {
        attribute headLightsTile: LightBeamTiltAngleValue[1];
    }
    attribute def LightBeamTiltAngleValue :> AngularMeasureValue {
        attribute angle: LightBeamTiltAngleValue :>> self {
            doc
            /*
             * Tilt angle shall be limited to the range between 50 and 80 degrees (inclusive).
             */

        }
        assert constraint { angle >= 50['°'] and angle <= 80['°'] }
    }
}
