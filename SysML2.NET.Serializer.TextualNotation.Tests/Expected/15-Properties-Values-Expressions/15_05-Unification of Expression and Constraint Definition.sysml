package '15_05-Unification of Expression and Constraint Definition' {
    private import '15_03-Value Expression'::*;
    private import ControlFunctions::forAll;
    private import SI::*;
    constraint def DiscBrakeConstraint { in wheelAssy: WheelAssy[4]; wheelAssy->forAll { in w : WheelAssy; 2* w.discBrakeAssy.radius < w.wheel.outerDiameter } }
    constraint def DiscBrakeFitConstraint_Alt { in discBrakeAssy: DiscBrakeAssy[1]; in wheel: Wheel[1]; 2* discBrakeAssy.radius < wheel.outerDiameter }
    part def Vehicle_2 {
        attribute mass: MassValue[1] = 1200[kg];
        attribute length: LengthValue[1] = 4.82[m];
        part wheelAssy: WheelAssy[4];
        constraint discBrakeConstraint: DiscBrakeConstraint { doc /*
         * This constraint is computed, but not asserted. This means a tool can identify 
         * when it is violated without the model being inconsistent.
         */
        in wheelAssy = Vehicle_2::wheelAssy; }
    }
    part def WheelAssy {
        part wheel: Wheel[1];
        part discBrakeAssy: DiscBrakeAssy[1];
        assert constraint discBrakeFitConstraint_Alt: DiscBrakeFitConstraint_Alt { doc /*
         * This constraint is asserted to be true, which means that the model
         * is inconsistent if it the constraint is violated.
         */
        in discBrakeAssy = WheelAssy::discBrakeAssy; in wheel = WheelAssy::wheel; }
    }
    part def DiscBrakeAssy {
        attribute radius: LengthValue[1] = 95[mm];
    }
}
