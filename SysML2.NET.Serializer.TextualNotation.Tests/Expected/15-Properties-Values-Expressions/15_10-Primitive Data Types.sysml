package '15.10-Primitive Data Types' {
    /*
     * Primitive data types are defined in normative model libraries.
     * Any more specialized data types can be declared in user-defined 
     * model libraries or models as needed.
     */
    private import ScalarValues::Integer {
        doc
        /*
         * The unqualified Integer is signed, in line with integer numbers in mathematics.
         */

    }
    private import ScalarValues::Natural;
    attribute def UnsignedInteger :> Natural {
        doc
        /* Mathematically, unsigned integers are just natural numbers (non-negative integers). */
    }
    private import ScalarValues::Real {
        doc
        /*
         * The unqualified Real is signed, in line with real numbers in mathematics.
         */

    }
    attribute def UnsignedReal :> Real {
        doc
        /*
         * Example of restriction of the base Real datatype.
         */

        attribute x: Real :>> self;
        assert constraint { x >= 0.0}
    }
    private import ScalarValues::String {
        doc
        /*
         * String attributes are sequences of characters.
         */

    }
    private import ScalarValues::Boolean {
        doc
        /*
         * Boolean type has two legal attributes: true, false.
         */

    }
    private import Time::DateTime;
    enum def ConditionColor {
        doc
        /*
         * Enumerations are defined as an implicit restriction of the extent of the
         * enumeration type to the listed enumeration values.
         * Note: Enumerations are currently limited to attributes.
         */

        enum red;
        enum yellow;
        enum green;
    }
    attribute def ConditionLevel {
        attribute associatedColor: ConditionColor;
    }
    enum def SeverityEnum :> ConditionLevel {
        enum danger {
            :>> associatedColor = ConditionColor::red;
        }
        enum warning {
            :>> associatedColor = ConditionColor::yellow;
        }
        enum normal {
            :>> associatedColor = ConditionColor::green;
        }
    }
    attribute def Diameter :> ISQ::LengthValue;
    enum def DiameterChoice :> Diameter {
        enum small = 60[SI::mm];
        enum medium = 70[SI::mm];
        enum large = 80[SI::mm];
    }
    attribute aperatureDiameter: DiameterChoice = DiameterChoice::small;
}
