package '10c-Fuel Economy Analysis' {
    private import ScalarValues::*;
    private import Quantities::*;
    private import MeasurementReferences::*;
    private import ISQ::*;
    private import USCU::*;
    attribute distancePerVolume: ScalarQuantityValue = length / volume;
    attribute gallon: MeasurementUnit = 231.0* ('in' ^ 3);
    package FuelEconomyRequirementsModel {
        requirement def FuelEconomyRequirement {
            attribute actualFuelEconomy :> distancePerVolume;
            attribute requiredFuelEconomy :> distancePerVolume;
            require constraint { actualFuelEconomy >= requiredFuelEconomy }
        }
        requirement cityFuelEconomyRequirement: FuelEconomyRequirement {
            :>> requiredFuelEconomy = 25[mi / gallon];
        }
        requirement highwayFuelEconomyRequirement: FuelEconomyRequirement {
            :>> requiredFuelEconomy = 30[mi / gallon];
        }
    }
    package VehicleDesignModel {
        part def Vehicle {
            attribute fuelEconomy_city :> distancePerVolume;
            attribute fuelEconomy_highway :> distancePerVolume;
            attribute cargoWeight: MassValue;
        }
        part def Engine;
        part def Transmission;
        part vehicle1_c1: Vehicle {
            part engine: Engine;
            part transmission: Transmission {
                exhibit state transmissionState {
                    entry;
                    then '1stGear';
                    state '1stGear';
                    then '2ndGear';
                    state '2ndGear';
                    then '3rdGear';
                    state '3rdGear';
                    then '4thGear';
                    state '4thGear';
                }
            }
        }
    }
    package FuelEconomyAnalysisModel {
        private import VehicleDesignModel::*;
        private import FuelEconomyRequirementsModel::*;
        attribute def ScenarioState {
            ref position: LengthValue;
            ref velocity: SpeedValue;
            ref acceleration: AccelerationValue;
            ref inclineAngle: AngularMeasureValue;
        }
        abstract calc def NominalScenario { in t: DurationValue; return : ScenarioState; }
        calc cityScenario: NominalScenario;
        calc highwayScenario: NominalScenario;
        analysis def FuelEconomyAnalysis {
            subject vehicle: Vehicle;
            in calc scenario: NominalScenario;
            in requirement fuelEconomyRequirement: FuelEconomyRequirement;
            return calculatedFuelEconomy: ScalarQuantityValue;
            objective fuelEconomyAnalysisObjective {
                doc
                /*
                 * The objective of this analysis is to determine whether the
                 * current vehicle design configuration can satisfy the fuel
                 * economy requirement.
                 */

                assume constraint { doc /*
                 * wheelDiameter == 33 inches
                 * drive train efficiency == 0.4
                 */
                }
                require fuelEconomyRequirement {
                    :>> actualFuelEconomy = calculatedFuelEconomy;
                }
            }
            action dynamicsAnalysis {
                /*
                 * Solve for the required engine power as a function of time
                 * to support the nominal scenarios.
                 *
                 * Note: Vehicle force = power/speed
                 * Note: EngineRPM * EngineGearRatio/WheelRPM = constant
                 */
            }
            action fuelConsumptionAnalysis {
                /*
                 * Solve the engine equations to determine how much fuel is
                 * consumed. The engine RPM is a function of the speed of the
                 * vehicle and the gear state.
                 */
            }
        }
        requirement vehicleFuelEconomyRequirementsGroup {
            subject vehicle: Vehicle;
            requirement vehicleFuelEconomyRequirement_city :> cityFuelEconomyRequirement {
                doc
                /*
                 * The vehicle shall provide a fuel economy that is greater than or equal to
                 * 25 miles per gallon for the nominal city driving scenarios.
                 */

                :>> actualFuelEconomy = vehicle.fuelEconomy_city;
                assume constraint { vehicle.cargoWeight == 1000[lb] }
            }
            requirement vehicleFuelEconomyRequirement_highway :> highwayFuelEconomyRequirement {
                doc
                /*
                 * The vehicle shall provide a fuel economy that is greater than or equal to
                 * 30 miles per gallon for the nominal highway driving scenarios.
                 */

                :>> actualFuelEconomy = vehicle.fuelEconomy_highway;
                assume constraint { vehicle.cargoWeight == 1000[lb] }
            }
        }
        part analysisContext {
            analysis cityFuelEconomyAnalysis: FuelEconomyAnalysis {
                subject vehicle = vehicle1_c1;
                in calc scenario = cityScenario;
                in requirement fuelEconomyRequirement = cityFuelEconomyRequirement;
            }
            analysis highwayFuelEconomyAnalysis: FuelEconomyAnalysis {
                subject vehicle = vehicle1_c1;
                in calc scenario = highwayScenario;
                in requirement fuelEconomyRequirement = highwayFuelEconomyRequirement;
            }
            part vehicle1_c1_analysized :> vehicle1_c1 {
                :>> fuelEconomy_city = cityFuelEconomyAnalysis.calculatedFuelEconomy;
                :>> fuelEconomy_highway = highwayFuelEconomyAnalysis.calculatedFuelEconomy;
            }
            assert satisfy vehicleFuelEconomyRequirementsGroup by vehicle1_c1_analysized;
        }
    }
}
