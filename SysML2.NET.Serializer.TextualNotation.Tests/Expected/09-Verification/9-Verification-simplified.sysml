package '9-Verification-simplified' {
    private import VerificationCases::*;
    private import Definitions::*;
    package Definitions {
        requirement def <'2'> MassRequirement {
            attribute massActual :> ISQ::mass;
            attribute massReqd :> ISQ::mass;
            doc
            /* The actual mass shall be less than or equal to the required mass limit. */
            require constraint { massActual <= massReqd }
        }
        part def Vehicle {
            attribute mass :> ISQ::mass;
        }
        part def MassVerificationSystem;
        part def Scale;
        part def TestOperator;
        individual def TestVehicle1 :> Vehicle;
        individual def TestVehicle2 :> Vehicle;
        individual def TestSystem :> MassVerificationSystem;
        verification def MassTest {
            objective massVerificationObjective {
                verify requirement massRequirement: '2';
            }
        }
    }
    package Usages {
        requirement <'2.1'> vehicleMassRequirement: '2' {
            subject vehicle: Vehicle;
            doc
            /* The vehicle mass shall be less than or equal to 2500 kg. */
            :>> massActual = vehicle.mass;
            :>> massReqd = 2500[SI::kg];
        }
        part vehicle1_c2: Vehicle;
        verification vehicleMassTest: MassTest {
            subject testVehicle: Vehicle;
            objective vehicleMassVerificationObjective {
                verify '2.1' :>> massRequirement;
            }
            action collectData {
                in part testVehicle: Vehicle = vehicleMassTest.testVehicle;
                out massMeasured :> ISQ::mass;
            }
            action processData {
                in massMeasured :> ISQ::mass = collectData.massMeasured;
                out massProcessed :> ISQ::mass;
            }
            action evaluateData {
                in massProcessed :> ISQ::mass = processData.massProcessed;
                out verdict: VerdictKind = PassIf('2.1'(vehicle = new testVehicle(mass = massProcessed)));
            }
            return verdict: VerdictKind = evaluateData.verdict;
        }
        part massVerificationSystem: MassVerificationSystem {
            perform vehicleMassTest {
                in part :>> testVehicle = vehicleUnderTest;
            }
            ref part vehicleUnderTest: Vehicle;
            part testOperator: TestOperator;
            part scale: Scale {
                perform vehicleMassTest.collectData {
                    in part :>> testVehicle;
                    ref measurement = testVehicle.mass;
                    out :>> massMeasured = measurement;
                }
            }
        }
        individual testSystem: TestSystem :> massVerificationSystem {
            timeslice test1 {
                ref individual :>> vehicleUnderTest : TestVehicle1 :> vehicle1_c2 {
                    :>> mass = 2500[SI::kg];
                }
            }
            then timeslice test2 {
                ref individual :>> vehicleUnderTest : TestVehicle2 :> vehicle1_c2 {
                    :>> mass = 2500[SI::kg];
                }
            }
        }
    }
}
